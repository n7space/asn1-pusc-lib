--!
--! Copyright (C) 2017-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-6-10 DEFINITIONS AUTOMATIC TAGS ::= BEGIN
EXPORTS ALL;
IMPORTS
    Memory-ID FROM Memory
    BytePointer FROM RawMemory
    PUSC-UINT32 FROM BasicTypes;

maxTM-6-10-DataAreaCount INTEGER ::= 65535

TM-6-10-CheckedRawMemoryDataReport
  ::= TM-6-10-CheckedRawMemoryDataReportGeneric {Memory-ID, TM-6-10-DataArea}
      (WITH COMPONENTS {memory-ID PRESENT})

TM-6-10-DataArea ::= TM-6-10-DataAreaGeneric {BytePointer, PUSC-UINT32}

TM-6-10-CheckedRawMemoryDataReportGeneric {Memory-ID-Type, DataArea-Type} ::= SEQUENCE
{
    memory-ID Memory-ID-Type OPTIONAL,
--! n UnsignedInteger-Type, moved to acn
    dataArea SEQUENCE (SIZE(1 .. maxTM-6-10-DataAreaCount)) OF DataArea-Type
}

TM-6-10-DataAreaGeneric {Address-Type, Length-Type} ::= SEQUENCE
{
    startAddress Address-Type,
    length Length-Type,
    checksum BIT STRING (SIZE (16))
}

END
