--!
--! Copyright (C) 2017-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-6-1 DEFINITIONS AUTOMATIC TAGS ::= BEGIN
EXPORTS ALL;
IMPORTS
    Base, BaseMultipleMemid FROM StructuredMemory
    Memory-ID FROM Memory
    MemoryData FROM Data
    PUSC-UINT32 FROM BasicTypes;

maxTC-6-1-LoadObjectInstructionCount INTEGER ::= 65535

TC-6-1-LoadObjectMemoryData ::= TC-6-1-LoadObjectMemoryDataGeneric {Base}

TC-6-1-LoadObjectMemoryDataMultipleMemid ::= TC-6-1-LoadObjectMemoryDataGeneric {BaseMultipleMemid}

LoadObjectInstruction ::= LoadObjectInstructionGeneric {PUSC-UINT32, MemoryData}
                          (WITH COMPONENTS {checksum PRESENT})

TC-6-1-LoadObjectMemoryDataGeneric {Base-Type} ::= SEQUENCE
{
--! memory-ID Memory-ID-Type, moved to acn
    base-ID Base-Type,
--! n UnsignedInteger-Type, moved to acn
    loadObjectInstructions SEQUENCE (SIZE(1 .. maxTC-6-1-LoadObjectInstructionCount)) OF LoadObjectInstruction
}

LoadObjectInstructionGeneric {UnsignedInteger-Type, VariableOctetString-Type} ::= SEQUENCE
{
    offset UnsignedInteger-Type,
    dataToLoad VariableOctetString-Type,
    checksum BIT STRING (SIZE(16)) OPTIONAL
}

END
