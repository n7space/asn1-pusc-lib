--!
--! Copyright (C) 2017-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-6-22 DEFINITIONS AUTOMATIC TAGS ::= BEGIN
EXPORTS ALL;
IMPORTS
    PUSC-UINT32 FROM BasicTypes
    Memory-ID FROM Memory
    Base, BaseMultipleMemid FROM StructuredMemory
    FilePath FROM FilePath;

maxTC-6-22-ObjectMemoryDumpCount INTEGER ::= 65535

TC-6-22-DumpObjectMemoryDataAreasToFile ::= TC-6-22-DumpObjectMemoryDataAreasToFileGeneric {Base, FilePath}

TC-6-22-DumpObjectMemoryDataAreasToFileMultipleMemid ::= TC-6-22-DumpObjectMemoryDataAreasToFileGeneric {BaseMultipleMemid, FilePath}

ObjectMemoryDump ::= ObjectMemoryDumpGeneric {PUSC-UINT32, PUSC-UINT32}

TC-6-22-DumpObjectMemoryDataAreasToFileGeneric {Base-Type, FilePath-Type} ::= SEQUENCE
{
--! memory-ID Memory-ID-Type, moved to acn
    base-ID Base-Type,
    filePath FilePath-Type,
--! n UnsignedInteger-Type, moved to acn
    objectMemoryDump SEQUENCE (SIZE(1 .. maxTC-6-22-ObjectMemoryDumpCount)) OF ObjectMemoryDump
}

ObjectMemoryDumpGeneric {UnsignedInteger-Type0, UnsignedInteger-Type1} ::= SEQUENCE
{
    offset UnsignedInteger-Type0,
    length UnsignedInteger-Type1
}

END
