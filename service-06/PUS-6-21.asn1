--!
--! Copyright (C) 2017-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-6-21 DEFINITIONS AUTOMATIC TAGS ::= BEGIN
EXPORTS ALL;
IMPORTS
    PUSC-UINT32 FROM BasicTypes
    Memory-ID FROM Memory
    Base, BaseMultipleMemid FROM StructuredMemory
    FilePath FROM FilePath;

maxTC-6-21-ObjectDataAreaCount INTEGER ::= 65535

TC-6-21-LoadObjectMemoryDataAreasByReference ::= TC-6-21-LoadObjectMemoryDataAreasByReferenceGeneric {Base, FilePath}

TC-6-21-LoadObjectMemoryDataAreasByReferenceMultipleMemid ::= TC-6-21-LoadObjectMemoryDataAreasByReferenceGeneric {BaseMultipleMemid, FilePath}

ObjectDataArea ::= ObjectDataAreaGeneric {PUSC-UINT32, PUSC-UINT32, PUSC-UINT32}
                   (WITH COMPONENTS {checksum PRESENT})

TC-6-21-LoadObjectMemoryDataAreasByReferenceGeneric {Base-Type, FilePath-Type} ::= SEQUENCE
{
--! memory-ID Memory-ID-Type OPTIONAL, moved to acn
    base-ID Base-Type,
    filePath FilePath-Type,
--! n UnsignedInteger-Type, moved to acn
    objectDataAreas SEQUENCE (SIZE(1 .. maxTC-6-21-ObjectDataAreaCount)) OF ObjectDataArea
}

ObjectDataAreaGeneric {UnsignedInteger-Type0, UnsignedInteger-Type1, UnsignedInteger-Type2} ::= SEQUENCE
{
    destinationOffset UnsignedInteger-Type0,
    offsetInFile UnsignedInteger-Type1,
    length UnsignedInteger-Type2,
    checksum BIT STRING (SIZE(16)) OPTIONAL
}


END
