--!
--! Copyright (C) 2017-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-6-2 DEFINITIONS AUTOMATIC TAGS ::= BEGIN
EXPORTS ALL;
IMPORTS
    PUSC-UINT32 FROM BasicTypes
    Memory-ID FROM Memory
    BytePointer FROM RawMemory
    MemoryData FROM Data;


maxTC-6-2-DataAreasCount INTEGER ::= 65535

TC-6-2-LoadRawMemoryDataAreas ::= TC-6-2-LoadRawMemoryDataAreasGeneric {Memory-ID, TC-6-2-DataArea}
                                  (WITH COMPONENTS {memory-ID PRESENT})

TC-6-2-DataArea ::= TC-6-2-DataAreaGeneric {BytePointer, MemoryData}

TC-6-2-LoadRawMemoryDataAreasGeneric {Memory-ID-Type, DataArea-Type} ::= SEQUENCE
{
    memory-ID Memory-ID-Type OPTIONAL,
--! n UnsignedInteger-Type,
    dataAreas SEQUENCE (SIZE(1 .. maxTC-6-2-DataAreasCount)) OF DataArea-Type
}

TC-6-2-DataAreaGeneric {Address-Type, Data-Type} ::= SEQUENCE
{
    startAddress Address-Type,
    dataToLoad Data-Type,
    checksum BIT STRING (SIZE (16)) OPTIONAL
}

END
