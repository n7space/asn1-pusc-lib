--!
--! Copyright (C) 2017-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-11-4 DEFINITIONS AUTOMATIC TAGS ::= BEGIN
EXPORTS ALL;
IMPORTS
    SubSchedule-ID FROM SubSchedule
    Group-ID FROM Group
    DummyType FROM Dummy
    PUSC-UINT32, AbsoluteTime FROM BasicTypes;

maxTC-11-4-ActivityCount INTEGER ::= 4095

TC-11-4-InsertActivitiesIntoTheTimeBasedSchedule ::= TC-11-4-InsertActivitiesIntoTheTimeBasedScheduleGeneric {SubSchedule-ID} (WITH COMPONENTS
{
    subschedule-ID PRESENT
})

TC-11-4-InsertActivitiesIntoTheTimeBasedScheduleGeneric {SubSchedule-ID-Type} ::= SEQUENCE
{
    subschedule-ID SubSchedule-ID OPTIONAL,
--! n UnsignedInteger, moved to acn
    activities SEQUENCE (SIZE(1 .. maxTC-11-4-ActivityCount)) OF TC-11-4-Activity
}

TC-11-4-Activity ::= TC-11-4-ActivityGeneric {Group-ID, AbsoluteTime, DummyType} (WITH COMPONENTS --! should be TC-Payload instead of DummyType but it is impossible to parameterize
{
    group-ID PRESENT
})

TC-11-4-ActivityGeneric {Group-ID-Type, AbsoluteTimeType, TC-PacketType} ::= SEQUENCE
{
    group-ID Group-ID-Type OPTIONAL,
    releaseTime AbsoluteTimeType,
    request TC-PacketType
}




END
