--!
--! Copyright (C) 2017-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-11-13 DEFINITIONS AUTOMATIC TAGS ::= BEGIN
EXPORTS ALL;
IMPORTS
    SubSchedule-ID FROM SubSchedule
    Group-ID FROM Group
    PUSC-UINT32, AbsoluteTime FROM BasicTypes
    Request-ID FROM Request;

maxTM-11-13-ReportCount INTEGER ::= 4095

TM-11-13-TimeBasedScheduleSummaryReport ::= SEQUENCE
{
--! n UnsignedInteger, moved to acn
    report SEQUENCE (SIZE(0 .. maxTM-11-13-ReportCount)) OF TM-11-13-Report
}

TM-11-13-Report ::= TM-11-13-ReportGeneric {SubSchedule-ID, Group-ID, AbsoluteTime, Request-ID} (WITH COMPONENTS
{
    subschedule-ID PRESENT,
    group-ID PRESENT
})

TM-11-13-ReportGeneric {SubSchedule-ID-Type, Group-ID-Type, AbsoluteTimeType, Request-ID-Type} ::= SEQUENCE
{
    subschedule-ID SubSchedule-ID-Type OPTIONAL,
    group-ID Group-ID-Type OPTIONAL,
    releaseTime AbsoluteTimeType,
    request-ID Request-ID-Type
}



END
