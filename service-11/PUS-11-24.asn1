--!
--! Copyright (C) 2017-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-11-24 DEFINITIONS AUTOMATIC TAGS ::= BEGIN
EXPORTS ALL;
IMPORTS
    PUSC-UINT32 FROM BasicTypes
    Group-ID FROM Group;

maxTC-11-24-GroupCount INTEGER ::= 4095

TC-11-24-EnableTimeBasedSchedulingGroups ::= TC-11-24-EnableTimeBasedSchedulingGroupsGeneric {Group-ID}

TC-11-24-EnableTimeBasedSchedulingGroupsGeneric {Group-ID-Type} ::= SEQUENCE
{
--! n UnsignedInteger, moved to acn
    groups SEQUENCE (SIZE(0 .. maxTC-11-24-GroupCount)) OF Group-ID-Type
}

END
