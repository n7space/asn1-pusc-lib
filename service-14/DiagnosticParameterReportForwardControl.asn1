--!
--! Copyright (C) 2017-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

DiagnosticParameterReportForwardControl DEFINITIONS AUTOMATIC TAGS ::= BEGIN
EXPORTS ALL;
IMPORTS
    ApplicationProcess-ID FROM ApplicationProcess
    PUSC-UINT32 FROM BasicTypes
    SubsamplingRate FROM SubsamplingRate
    DiagnosticParameterReportStructure-ID FROM DiagnosticParameterReportStructure;


maxDiagnosticParameterReportForwardControlCount INTEGER ::= 4095
maxDiagnosticStructure-ID-Count INTEGER ::= 4095

DiagnosticParameterReportForwardControlSubsampling ::= DiagnosticParameterReportForwardControlGeneric
{SingleDiagnosticParameterReportForwardControlSubsampling}

DiagnosticParameterReportForwardControlNoSubsampling ::= DiagnosticParameterReportForwardControlGeneric
{SingleDiagnosticParameterReportForwardControlNoSubsampling}

SingleDiagnosticParameterReportForwardControlSubsampling ::= SingleDiagnosticParameterReportForwardControlGeneric
{ApplicationProcess-ID, DiagnosticParameterStructure-ID-ConfigurationSubsampling}

SingleDiagnosticParameterReportForwardControlNoSubsampling ::= SingleDiagnosticParameterReportForwardControlGeneric
{ApplicationProcess-ID, DiagnosticParameterStructure-ID-ConfigurationNoSubsampling}

DiagnosticParameterStructure-ID-ConfigurationNoSubsampling ::= DiagnosticParameterStructure-ID-ConfigurationGeneric
{DiagnosticParameterReportStructure-ID, NULL}
(WITH COMPONENTS
{
    subsamplingRate ABSENT
})

DiagnosticParameterStructure-ID-ConfigurationSubsampling ::= DiagnosticParameterStructure-ID-ConfigurationGeneric
{DiagnosticParameterReportStructure-ID, NULL}
(WITH COMPONENTS
{
    subsamplingRate PRESENT
})

DiagnosticParameterReportForwardControlGeneric {SingleDiagnosticParameterReportForwardControlType} ::= SEQUENCE
{
--! n1 UnsignedInteger,
    forwardControl SEQUENCE (SIZE(1 .. maxDiagnosticParameterReportForwardControlCount)) OF SingleDiagnosticParameterReportForwardControlType
}

SingleDiagnosticParameterReportForwardControlGeneric {ApplicationProcess-ID-Type, DiagnosticParameterStructure-ID-Type} ::= SEQUENCE
{
    applicationProcess-ID ApplicationProcess-ID-Type,
--! n2 UnsignedInteger,
    structure SEQUENCE (SIZE(0 .. maxDiagnosticStructure-ID-Count)) OF type DiagnosticParameterStructure-ID-Type
}

DiagnosticParameterStructure-ID-ConfigurationGeneric {DiagnosticParameterStructure-ID-Type, SubsamplingRateType} ::= SEQUENCE
{
    id DiagnosticParameterStructure-ID-Type,
    subsamplingRate SubsamplingRateType OPTIONAL
}

END
