--!
--! Copyright (C) 2017-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-4-9 DEFINITIONS AUTOMATIC TAGS ::= BEGIN
EXPORTS ALL;
IMPORTS
    ReportingInterval, SamplingInterval FROM Intervals
    Parameter-ID FROM Parameter
    ParameterStatisticsDefinition FROM ParameterStatisticsDefinitions
    PUSC-UINT32 FROM BasicTypes;

maxTM-4-9-ParameterStatisticCount INTEGER ::= 65535

TM-4-9-ParameterStatisticsDefinitionReport
    ::= TM-4-9-ParameterStatisticsDefinitionReportGeneric {ReportingInterval}
        (WITH COMPONENTS {reportingInterval PRESENT})

TM-4-9-ParameterStatisticsDefinitionReportGeneric {ReportingInterval-Type} ::= SEQUENCE
{
    reportingInterval ReportingInterval-Type OPTIONAL,
--! n UnsignedInteger, moved to acn
    parameterStatistics SEQUENCE (SIZE(1 .. maxTM-4-9-ParameterStatisticCount)) OF ParameterStatisticsDefinition
}

END
