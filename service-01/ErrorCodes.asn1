--!
--! Copyright (C) 2017-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

ErrorCodes DEFINITIONS AUTOMATIC TAGS ::= BEGIN
EXPORTS ALL;

AcceptanceFailureCode ::= ENUMERATED {error1 (1)}
AcceptanceFailureData ::= CHOICE
{
    error1 BIT STRING (SIZE(1))
}
AcceptanceFailureNotice ::= SEQUENCE
{
    data AcceptanceFailureData
}

ExecutionStartFailureCode ::= ENUMERATED {error1 (1)} 
ExecutionStartFailureData ::= CHOICE
{
    error1 BIT STRING (SIZE(1))
}
ExecutionStartFailureNotice ::= SEQUENCE
{
    data ExecutionStartFailureData
}

ExecutionProgressFailureCode ::= ENUMERATED {error1 (1)}
ExecutionProgressFailureData ::= CHOICE
{
    error1 BIT STRING (SIZE(1))
}
ExecutionProgressFailureNotice::= SEQUENCE
{
    data ExecutionProgressFailureData
}

ExecutionCompletionFailureCode ::= ENUMERATED {error1 (1)}
ExecutionCompletionFailureData ::= CHOICE
{
    error1 BIT STRING (SIZE(1))
}
ExecutionCompletionFailureNotice ::= SEQUENCE
{
    data ExecutionCompletionFailureData
}

RoutingFailureCode ::= ENUMERATED {error1 (1)}
RoutingFailureData ::= CHOICE
{
    error1 BIT STRING (SIZE(1))
}
RoutingFailureNotice ::= SEQUENCE
{
    data RoutingFailureData
}

END
