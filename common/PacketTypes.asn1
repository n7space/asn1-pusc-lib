--!
--! Copyright (C) 2017 N7 Mobile sp. z o. o.
--! Contact: http://n7mobile.pl/Space
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PacketTypes DEFINITIONS ::= BEGIN
EXPORTS ALL;
IMPORTS
    PUSC-UINT, PUSC-BOOL FROM BasicTypes
    ApplicationProcess-ID FROM ApplicationProcess;


ApplicationProcess-ID-Packet ::= ApplicationProcess-ID
SecondaryHeaderFlag ::= PUSC-BOOL

Packet-ID {PacketType} ::= SEQUENCE
{
    packetType PacketType,
    secondaryHeaderFlag SecondaryHeaderFlag,
    applicationProcess-ID ApplicationProcess-ID-Packet
}

TM-Packet-ID ::= Packet-ID {NULL}
TC-Packet-ID ::= Packet-ID {NULL}

PacketSequenceControl ::= SEQUENCE
{
    sequenceFlags NULL,
    packetSequenceCount PUSC-UINT (0 .. 16383)
}

PacketVersionNumber ::= NULL

END
