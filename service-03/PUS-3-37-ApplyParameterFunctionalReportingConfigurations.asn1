--!
--! Copyright (C) 2017 N7 Mobile sp. z o. o.
--! Contact: http://n7mobile.pl/Space
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-3-37-ApplyParameterFunctionalReportingConfigurations DEFINITIONS AUTOMATIC TAGS ::= BEGIN
EXPORTS ALL;
IMPORTS
    ParameterFunctionalReportingDefinition-ID FROM ParameterFunctionalReportingDefinition
    PUSC-UINT32 FROM BasicTypes;

TC-3-37-ApplyParameterFunctionalReportingConfigurations ::= SEQUENCE
{
    configurationExecutionFlag ConfigurationExecutionFlag,
--! n PUSC-UINT32, moved to acn
    parameterFunctionalReportingDefinition-ID SEQUENCE (SIZE(0 .. 2147483647)) OF ParameterFunctionalReportingDefinition-ID
}

ConfigurationExecutionFlag ::= ENUMERATED
{
    non-exclusive (0),
    exclusive (1)
}

END
