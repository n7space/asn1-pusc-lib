--!
--! Copyright (C) 2017 N7 Mobile sp. z o. o.
--! Contact: http://n7mobile.pl/Space
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-3-32-ModifyTheCollectionIntervalOfDiagnosticParameterReportStructures DEFINITIONS AUTOMATIC TAGS ::= BEGIN
EXPORTS ALL;
IMPORTS
    PUSC-UINT32 FROM BasicTypes
    DiagnosticParameterReportStructure-ID FROM DiagnosticParameterReportStructure
    CollectionInterval FROM CollectionInterval;

PC-3-32-ModifyTheCollectionIntervalOfDiagnosticParameterReportStructures ::= SEQUENCE
{
--! n PUSC-UINT32, moved to acn
    diagnosticParamererReportStructureIntervals SEQUENCE (SIZE(0 .. 2147483647)) OF DiagnosticParameterReportStructureIntervals
}

DiagnosticParameterReportStructureIntervals ::= SEQUENCE
{
    diagnosticParameterReportStructure-ID DiagnosticParameterReportStructure-ID,
    collectionInterval CollectionInterval
}

END
