--!
--! Copyright (C) 2017-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-3-44 DEFINITIONS AUTOMATIC TAGS ::= BEGIN
EXPORTS ALL;
IMPORTS
    PUSC-UINT32 FROM BasicTypes
    ApplicationProcess-ID FROM ApplicationProcess
    ParameterReportStructureType,
    ParameterReportStructure-ID FROM ParameterReportStructureType
    PeriodicGenerationActionStatus FROM PeriodicGenerationActionStatus
    CollectionInterval FROM CollectionInterval
    ParameterFunctionalReportingDefinition-ID FROM ParameterFunctionalReportingDefinition
    ParameterReportingEntries FROM ParameterReportingEntries;

macTC-44-ParameterReportingEntryCount INTEGER ::= 536870911
maxTC-44-ApidParameterReportingEntryCount INTEGER ::= 536870911

TC-3-44-ModifyThePeriodicGenerationPropertiesOfParameterReportDefinitionsOfAParameterFunctionalReportingDefinitionMultipleApid ::= TC-3-44-ModifyThePeriodicGenerationPropertiesOfParameterReportDefinitionsOfAParameterFunctionalReportingDefinitionMultipleApidGeneric {ParameterFunctionalReportingDefinition-ID}

TC-3-44-ModifyThePeriodicGenerationPropertiesOfParameterReportDefinitionsOfAParameterFunctionalReportingDefinitionMultipleApidGeneric {ParameterFunctionalReportingDefinition-ID-Type} ::= SEQUENCE
{
    parameterFunctionalReportingDefinition-ID ParameterFunctionalReportingDefinition-ID-Type,
--! n1 UnsignedInteger-Type, moved to acn
    apidParameterReportingEntries SEQUENCE (SIZE(1 .. maxTC-44-ApidParameterReportingEntryCount)) OF TC-3-44-ApidParameterReportingEntries
}

TC-3-44-ModifyThePeriodicGenerationPropertiesOfParameterReportDefinitionsOfAParameterFunctionalReportingDefinition ::= TC-3-44-ModifyThePeriodicGenerationPropertiesOfParameterReportDefinitionsOfAParameterFunctionalReportingDefinitionGeneric {ParameterFunctionalReportingDefinition-ID}

TC-3-44-ModifyThePeriodicGenerationPropertiesOfParameterReportDefinitionsOfAParameterFunctionalReportingDefinitionGeneric {ParameterFunctionalReportingDefinition-ID-Type} ::= SEQUENCE
{
    parameterFunctionalReportingDefinition-ID ParameterFunctionalReportingDefinition-ID-Type,
--! n2 UnsignedInteger-Type, moved to acn
    parameterReportingEntries SEQUENCE (SIZE(1 .. macTC-44-ParameterReportingEntryCount)) OF ParameterReportingEntries
}

TC-3-44-ApidParameterReportingEntries ::= TC-3-44-ApidParameterReportingEntriesGeneric {ApplicationProcess-ID}

TC-3-44-ApidParameterReportingEntriesGeneric {TApplicationProcess-ID} ::= SEQUENCE
{
    applicationProcess-ID ApplicationProcess-ID,
--! n2 UnsignedInteger, moved to acn
    parameterReportingEntries SEQUENCE (SIZE(1 .. macTC-44-ParameterReportingEntryCount)) OF ParameterReportingEntries
}

END
