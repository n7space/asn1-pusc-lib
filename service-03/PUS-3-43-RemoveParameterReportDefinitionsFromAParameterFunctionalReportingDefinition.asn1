--!
--! Copyright (C) 2017 N7 Mobile sp. z o. o.
--! Contact: http://n7mobile.pl/Space
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-3-43-RemoveParameterReportDefinitionsFromAParameterFunctionalReportingDefinition DEFINITIONS AUTOMATIC TAGS ::= BEGIN
EXPORTS ALL;
IMPORTS
    ApplicationProcess-ID FROM ApplicationProcess
    PUSC-UINT32 FROM BasicTypes
    ParameterFunctionalReportingDefinition-ID FROM ParameterFunctionalReportingDefinition
    ParameterReportStructureType,
    ParameterReportStructure-ID FROM ParameterReportStructureType;

TC-3-43-RemoveParameterReportDefinitionsFromAParameterFunctionalReportingDefinitionMultipleApid ::= SEQUENCE
{
    parameterFunctionalReportingDefinition-ID ParameterFunctionalReportingDefinition-ID,
--! n1 PUSC-UINT32, moved to acn
    apidParameterReportingDefinitions SEQUENCE (SIZE(0 .. 536870911)) OF ApidParameterReporingDefinitions
}

TC-3-43-RemoveParameterReportDefinitionsFromAParameterFunctionalReportingDefinition ::= SEQUENCE
{
    parameterFunctionalReportingDefinitions-ID ParameterFunctionalReportingDefinition-ID,
--! n2 PUSC-UINT32, moved to acn
    parameterReportingDefinitions SEQUENCE (SIZE(0 .. 536870911)) OF ParameterReportingDefiniton
}

ApidParameterReporingDefinitions ::= SEQUENCE
{
    applicationProcess-ID ApplicationProcess-ID,
--! n2 PUSC-UINT32, moved to acn
    parameterReportingDefinitions SEQUENCE (SIZE(0 .. 536870911)) OF ParameterReportingDefiniton
}

ParameterReportingDefiniton ::= SEQUENCE
{
--! parameterReportStructureType ParameterReportStructureType, moved to acn
    parameterReportStructure-ID ParameterReportStructure-ID
}

END
