--!
--! Copyright (C) 2017-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

ParameterMonitoringDefinition DEFINITIONS AUTOMATIC TAGS ::= BEGIN
EXPORTS ALL;
IMPORTS
    PUSC-UINT32 FROM BasicTypes
    DummyType FROM Dummy
    PMON-ID, PMON-CheckType FROM PMON
    Parameter-ID, ParameterValue, ParameterMask FROM Parameter
    EventDefinition-ID, eventDefinition-ID-Size FROM EventDefinition
    CheckValidityCondition FROM CheckValidityCondition;


ParameterMonitoringDefinition ::= ParameterMonitoringDefinitionGeneric
{PMON-ID, Parameter-ID, CheckValidityCondition, PUSC-UINT32, PUSC-UINT32}
(WITH COMPONENTS
{
    checkValidityCondition PRESENT,
    monitoringInterval PRESENT
})

TC-12-7-ParameterMonitoringDefinition ::= ParameterMonitoringDefinitionGeneric
{PMON-ID, Parameter-ID, CheckValidityCondition, PUSC-UINT32, PUSC-UINT32}
(WITH COMPONENTS
{
    checkValidityCondition ABSENT,
    monitoringInterval ABSENT
})

ExpectedValueCheckingCriteria ::= ExpectedValueCheckingCriteriaGeneric
{DummyType, EventDefinitionSpare, DummyType, EventDefinition-ID}
(WITH COMPONENTS
{
    spare PRESENT
})

LimitCheckingCriteria ::= LimitCheckingCriteriaGeneric {EventDefinition-ID, DummyType}

DeltaCheckingCriteria ::= DeltaCheckingCriteriaGeneric{EventDefinition-ID, DummyType, PUSC-UINT32}

EventDefinitionSpare ::= BIT STRING (SIZE(eventDefinition-ID-Size))

ParameterMonitoringDefinitionGeneric {PMON-ID-Type, Parameter-ID-Type, CheckValidityConditionType, MonitoringIntervalType, RepetitionNumberType} ::= SEQUENCE
{
    pmon-ID PMON-ID-Type,
    monitoredParameter-ID Parameter-ID-Type,
    checkValidityCondition CheckValidityConditionType OPTIONAL,
    monitoringInterval MonitoringIntervalType OPTIONAL,
    repetitionNumber RepetitionNumberType,
--!    checkType CheckType-Type,
    checkTypeCriteria CheckTypeCriteria
}

CheckTypeCriteria ::= CHOICE
{
    expectedValueChecking ExpectedValueCheckingCriteria,
    limitChecking LimitCheckingCriteria,
    deltaChecking DeltaCheckingCriteria
}

ExpectedValueCheckingCriteriaGeneric {MaskType, SpareType, ExpectedValueType, EventDefinition-ID-Type} ::= SEQUENCE
{
    mask MaskType,
    spare SpareType OPTIONAL,
    expectedValue ExpectedValueType,
    eventDefinition-ID EventDefinition-ID-Type
}

LimitCheckingCriteriaGeneric {EventDefinition-ID-Type, LimitType} ::= SEQUENCE
{
    lowLimit LimitType,
    lowLimitEventDefinition-ID EventDefinition-ID-Type,
    highLimit LimitType,
    highLimitEventDefinition EventDefinition-ID-Type
}

DeltaCheckingCriteriaGeneric {EventDefinition-ID-Type, DeltaThresholdType, UnsignedIntegerType} ::= SEQUENCE
{
    lowDeltaThreshold DeltaThresholdType,
    lowThresholdEventDefinition-ID EventDefinition-ID-Type,
    highDeltaThreshold DeltaThresholdType,
    highThresholdEventDefinition-ID EventDefinition-ID-Type,
    numberOFConstructiveDeltaValues UnsignedIntegerType
}

END

/*ParameterMonitoringDefinition DEFINITIONS AUTOMATIC TAGS ::= BEGIN
EXPORTS ALL;
IMPORTS
    PUSC-UINT32 FROM BasicTypes
    PMON-ID, PMON-CheckType FROM PMON
    Parameter-ID, ParameterValue, ParameterMask FROM Parameter
    EventDefinition-ID, eventDefinition-ID-Size FROM EventDefinition
    CheckValidityCondition FROM CheckValidityCondition;


ParameterMonitoringDefinition ::= ParameterMonitoringDefinitionGeneric {PMON-ID, CheckValidityCondition, PUSC-UINT32, PUSC-UINT32} (WITH COMPONENTS
{
    checkValidityCondition PRESENT,
    monitoringInterval PRESENT
})


LimitCheckingCriteria ::= LimitCheckingCriteriaGeneric {EventDefinition-ID, ParameterValue}

DeltaCheckingCriteria ::= DeltaCheckingCriteriaGeneric{EventDefinition-ID, ParameterValue, PUSC-UINT32}

EventDefinitionSpare ::= BIT STRING (SIZE(eventDefinition-ID-Size))



ParameterMonitoringDefinitionGeneric {PMON-ID-Type, CheckValidityConditionType, MonitoringIntervalType, RepetitionNumberType} ::= SEQUENCE
{
    pmon-ID PMON-ID-Type,
--!    monitoredParameter-ID Parameter-ID-Type,
    checkValidityCondition CheckValidityConditionType OPTIONAL,
    monitoringInterval MonitoringIntervalType OPTIONAL,
    repetitionNumber RepetitionNumberType,
--!    checkType CheckType-Type,
    checkTypeCriteria CheckTypeCriteria
}

CheckTypeCriteria ::= CHOICE
{
    expectedValueChecking ExpectedValueCheckingCriteria,
    limitChecking LimitCheckingCriteria,
    deltaChecking DeltaCheckingCriteria
}

ExpectedValueCheckingCriteria ::= ExpectedValueCheckingCriteriaGeneric {ParameterMask, EventDefinitionSpare, ParameterValue, EventDefinition-ID} (WITH COMPONENTS
{
    spare PRESENT
})

ExpectedValueCheckingCriteriaGeneric {MaskType, SpareType, ExpectedValueType, EventDefinition-ID-Type} ::= SEQUENCE
{
    mask MaskType,
    spare SpareType OPTIONAL,
    expectedValue ExpectedValueType,
    eventDefinition-ID EventDefinition-ID-Type
}

LimitCheckingCriteriaGeneric {EventDefinition-ID-Type, LimitType} ::= SEQUENCE
{
    lowLimit LimitType,
    lowLimitEventDefinition-ID EventDefinition-ID-Type,
    highLimit LimitType,
    highLimitEventDefinition EventDefinition-ID-Type
}

DeltaCheckingCriteriaGeneric {EventDefinition-ID-Type, DeltaThresholdType, UnsignedIntegerType} ::= SEQUENCE
{
    lowDeltaThreshold DeltaThresholdType,
    lowThresholdEventDefinition-ID EventDefinition-ID-Type,
    highDeltaThreshold DeltaThresholdType,
    highThresholdEventDefinition-ID EventDefinition-ID-Type,
    numberOFConstructiveDeltaValues UnsignedIntegerType
}

END*/
