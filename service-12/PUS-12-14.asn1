--!
--! Copyright (C) 2017-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-12-14 DEFINITIONS ::= BEGIN
EXPORTS ALL;
IMPORTS
    PMON-Status, PMON-ID FROM PMON
    PUSC-UINT32 FROM BasicTypes;

maxTM-12-14-ParameterMonitoringStatusCount INTEGER ::= 4095

TM-12-14-ParameterMonitoringDefinitionReport ::= SEQUENCE
{
--! n BasicTypes.PUSC-UINT32,
    status SEQUENCE (SIZE(0 .. maxTM-12-14-ParameterMonitoringStatusCount )) OF ParameterMonitoringStatusReport
}

ParameterMonitoringStatusReport ::= ParameterMonitoringStatusReportGeneric {PMON-ID}

ParameterMonitoringStatusReportGeneric {PMON-ID-Type} ::= SEQUENCE
{
    pmon-ID PMON-ID-Type,
    pmonStatus PMON-Status
}

END
