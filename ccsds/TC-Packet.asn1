--!
--! Copyright (C) 2017-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

TC-Packet DEFINITIONS AUTOMATIC TAGS ::= BEGIN
EXPORTS ALL;
IMPORTS
    CCSDS-Packet,
    PacketDataField,
    Packet-ID,
    DataWithSecondaryHeader,
    DataNoSecondaryHeader,
    SecondaryHeaderFlag FROM PacketTypes
    ApplicationProcess-ID FROM ApplicationProcess
    ApplicationProcessUser-ID FROM ApplicationProcessUser
    TC-Payload, TC-NoHeaderPayload FROM TC-Payload
    ServiceType-ID, MessageSubtype-ID FROM MessageType;

TC-CCSDS-Packet ::= CCSDS-Packet {TC-Packet-ID, TC-PacketDataField}

TC-PacketDataField ::= PacketDataField {TC-DataWithSecondaryHeader, TC-DataNoSecondaryHeader}

TC-DataNoSecondaryHeader ::= DataNoSecondaryHeader {TC-NoHeaderPayload}
    (WITH COMPONENTS {packetErrorControl PRESENT})

TC-DataWithSecondaryHeader ::= DataWithSecondaryHeader {TC-PacketSecondaryHeader, TC-Payload}
    (WITH COMPONENTS {packetErrorControl PRESENT})

TC-Packet-ID ::= Packet-ID {TC-PacketType}

TC-PacketSecondaryHeader ::=  SEQUENCE
{
--! tcPacketPusVersionNumber,                   moved to ACN
    acknowledgementFlags AcknowledgementFlags,
--! serviceType-ID ServiceType-ID,              moved to ACN
--! messageSubtype-ID MessageSubtype-ID,        moved to ACN
    source-ID ApplicationProcessUser-ID
--! spare NULL         defined as align-to-next in acn file
}

AcknowledgementFlags ::= SEQUENCE
{
    ackExecutionCompletion BOOLEAN,
    ackExecutionProgress BOOLEAN,
    ackExecutionStart BOOLEAN,
    ackAcceptance BOOLEAN
}

TC-PacketType ::= NULL

END
