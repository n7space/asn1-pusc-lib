--!
--! Copyright (C) 2018-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

Storage-ControlConfiguration DEFINITIONS AUTOMATIC TAGS ::= BEGIN
EXPORTS ALL;

maxConfigurationSize Storage-ControlConfigurationSizeType ::= 4095
Storage-ControlConfiguration {PacketStore-ID-Type, Configuration-Type} ::= SEQUENCE
{
    packetStoreID PacketStore-ID-Type,
    configuration SEQUENCE(SIZE(0 .. maxConfigurationSize)) OF Configuration-Type
}

maxTailSize Storage-ControlConfigurationSizeType ::= 4095
Storage-ControlConfigurationItem {ApplicationProcess-ID-Type, Tail-Type} ::= SEQUENCE
{
    applicationProcess-ID ApplicationProcess-ID-Type OPTIONAL,
    tail SEQUENCE(SIZE(0 .. maxTailSize)) OF Tail-Type
}

Storage-ControlParameterReportItem {Parameter-Type, SubsamplingRate-Type} ::= SEQUENCE
{
    parameter Parameter-Type,
    subsamplingRate SubsamplingRate-Type OPTIONAL
}

Storage-ControlConfigurationSizeType ::= INTEGER

END
