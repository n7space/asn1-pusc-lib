--!
--! Copyright (C) 2018-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

Storage-ControlReportType DEFINITIONS AUTOMATIC TAGS ::= BEGIN
EXPORTS ALL;
IMPORTS
    Storage-ControlConfiguration, Storage-ControlConfigurationItem, Storage-ControlConfigurationSizeType FROM Storage-ControlConfiguration
    PacketStore-ID FROM PacketStore
    ApplicationProcess-ID FROM ApplicationProcess
    MessageSubtype-ID FROM MessageType
    PUSC-UINT32 FROM BasicTypes;

Storage-ControlReportType ::=
    Storage-ControlConfiguration {PacketStore-ID, Storage-ControlReportTypeStorage-ControlConfiguration}

Storage-ControlReportTypeStorage-ControlConfiguration ::=
    Storage-ControlConfigurationItem {ApplicationProcess-ID, Storage-ControlReportTypeMessageSubtypes}

Storage-ControlReportTypeMessageSubtypes ::= Storage-ControlReportTypeMessageSubtypesGeneric {MessageSubtype-ID}

maxMessageSubtypeSize INTEGER ::= 4096
Storage-ControlReportTypeMessageSubtypesGeneric {MessageSubtype-Type} ::= SEQUENCE
{
    messageSubtype SEQUENCE(SIZE(0 .. maxMessageSubtypeSize)) OF MessageSubtype-Type
}

END
