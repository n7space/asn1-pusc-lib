--!
--! Copyright (C) 2018-2024 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-15-15 DEFINITIONS AUTOMATIC TAGS ::= BEGIN
EXPORTS ALL;
IMPORTS
    PacketStore-ID FROM PacketStore
    PacketStoreRetrievalPriority FROM PacketStoreEnumerations
    PUSC-UINT32 FROM BasicTypes;

TC-15-15-ResumeTheOpenRetrievalOfPacketStores ::= TC-15-15-ResumeTheOpenRetrievalOfPacketStoresGeneric {TC-15-15-PacketStoresToResume}

maxPacketStoresToResumeSize INTEGER ::= 4096
TC-15-15-ResumeTheOpenRetrievalOfPacketStoresGeneric {PacketStoresToResume-Type} ::= SEQUENCE
{
    packetStoresToResume SEQUENCE(SIZE(1 .. maxPacketStoresToResumeSize)) OF PacketStoresToResume-Type
}

TC-15-15-PacketStoresToResume ::= TC-15-15-PacketStoresToResumeGeneric {PacketStore-ID, PacketStoreRetrievalPriority}
TC-15-15-PacketStoresToResumeGeneric {PacketStore-ID-Type, RetrievalPriority-Type} ::= SEQUENCE
{
    packetStore-ID PacketStore-ID-Type,
    retrievalPriority RetrievalPriority-Type OPTIONAL
}

END
