--!
--! Copyright (C) 2017 N7 Mobile sp. z o. o.
--! Contact: http://n7mobile.pl/Space
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!


LargeMessageTransaction DEFINITIONS AUTOMATIC TAGS ::= BEGIN
EXPORTS ALL;
IMPORTS
    PUSC-UINT32 FROM BasicTypes;

LargeMessageTransactionIdentifierType ::= PUSC-UINT32

PartReportGeneric { UnsignedInteger, PartType } ::= SEQUENCE
{
    largeMessageTransactionIdentifier LargeMessageTransactionIdentifierType, --! must be unique
    partSequenceNumber UnsignedInteger,
    part PartType
}

--! The "maxPartSizeTransfer" should be deduced from ccsds max packet lenght (and header size) and
--! should be variable depending on subservice number - sbs 11 and 3 require shortened length
--! depending on another external factor - so it should be of variable length
--! TODO: refactor this draft to address above changes
maxPartSizeTransfer INTEGER ::= 4096

PartSizeOctedStringType ::= OCTET STRING (SIZE(maxPartSizeTransfer))

UplinkPartReport ::= PartReportGeneric {PUSC-UINT32, PartSizeOctedStringType}
DownlinkPartReport ::= PartReportGeneric {PUSC-UINT32, PartSizeOctedStringType}

END
